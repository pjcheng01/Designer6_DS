;;;┌────────────────────────────────┐
 ;;;│  程  式 :Lt2000版                                              │
 ;;;│  主程式 :screwline                                             │
 ;;;│  日  期 :89.11.14                                              │
 ;;;│  姓  名 :jacky                                                 │
 ;;;│  對話框 :                                                      │
 ;;;│  方  法 :                                                      │
 ;;;│  相關檔案:                                                     │
 ;;;└────────────────────────────────┘
(defun c:screwline()
       (setq pro_flag 1)
       (setq lsp_outscrewleng nil)
       (setq lsp_pitch        nil)
       (setq cmdecho_v (getvar "cmdecho"))
       
       (setvar "cmdecho" 0)

  
       (setq #path_dcl Powdesign_DCL_PATH)
       (actdcl (strcat #path_dcl "screwline") "screwline")
       
       (sel_show_sld "endcir" "endc_phL")
       (action_tile "endcir"     "(sel_show_sld \"endcir\" \"endc_phL\")(setq pro_flag 1)")
       (action_tile "endflat"    "(sel_show_sld \"endflat\" \"endf_phL\")(setq pro_flag 2)")
       (action_tile "endnone"    "(sel_show_sld \"endnone\" \"endn_phL\")(setq pro_flag 3)")
         
     
       (action_tile "accept" "(setq lsp_outscrewleng  (get_tile \"outscrewleng\"))(setq lsp_pitch (/ (atof (get_tile \"pitch\")) 2))(done_dialog)");---2003.03.10 SAM---
       (action_tile "cancel" "(done_dialog)(unload_dialog dcL_id)")
       (start_dialog)
  
       (if (and (/= lsp_pitch "")
		(/= lsp_pitch nil)
		(/= lsp_pitch 0) 
           );and
	   (progn
	        (cond ( (= pro_flag 2)
		        (endflatpro)
		      )
		      ( (or (= pro_flag 1)
			    (= pro_flag 3)
			);or    
		        (endcirpro)
		      )
		      
		 );cond
	    );progn
	    (progn
	         (alert "\n牙距(Pitch)資料空白\n")
	         (exit)
	    );progn  
	);if 
		
       
      ; (if (= exe_st 1)
      ;	   (c:screwline)
      ; );if	 
       (setvar "cmdecho" cmdecho_v)
       (setvar "osmode" osmode_v)
       (princ)
  );defun

  (defun endflatpro(/   all_pitch_flag p1 p2 p3 p4 a90 all_leng ang_bp1_p2 ang_bp2_p1 dist_p1_p2 sin_p1p2 cos_p1p2 p2x p2y p4x p4y
                       p3x p3y c_temp1 c_temp2 expt_a2b2 p2_p4_vdist p3_p4_vdist p11 p12 p11end ang_bp11_p1 inter_p
		       ss
		   )
       (setq a90 (/ pi 2))
       (setq all_leng nil)
       (setq all_pitch_flag nil)
      
       (princ "\n請依照對話框幻燈片 P1 P2 P3 P4 之位置輸入\n")
       (setq p1 (getpoint "\np1 (全牙邊線與中心線之交點): "))
       (setq p2 (getpoint p1 "\np2 (平形端底線與中心線之交點): "))
       (setq p3 (getpoint p2 "\np3 (平形端削角線與平形端底線之交點): "))
       (setq p4 (getpoint p3 "\np4 (平形端削角線與外框線之交點): "))
       (setq osmode_v (getvar "osmode"))
       (setvar "osmode" 0)
       (setq ang_bp1_p2 (angle p1 p2));b:base
       (setq ang_bp2_p1 (angle p2 p1))
       (setq dist_p1_p2 (distance p1 p2))
       (if (= lsp_outscrewleng "")
	   (progn
	        (setq lsp_outscrewleng (rtos dist_p1_p2))
	        (setq all_pitch_flag t)
	   );progn  
       );if	 
       (cond ( (>=  (atof lsp_outscrewleng) dist_p1_p2)
	       (setq dist_p1_p2 dist_p1_p2)
	       (setq all_pitch_flag t) 
	       
             )
    
             ( (<  (atof lsp_outscrewleng) dist_p1_p2)
	  
	        (setq dist_p1_p2 (atoi lsp_outscrewleng))
	        (setq p1 (polar p2 ang_bp2_p1 dist_p1_p2))
	   
             )
       );cond	     
    
      
       (setq sin_p1p2 (sin ang_bp1_p2))
       (setq cos_p1p2 (cos ang_bp1_p2))
    
       (setq p2x (car p2))
       (setq p2y (cadr p2))
       (setq p4x (car p4))
       (setq p4y (cadr p4))
       (setq c_temp1 (- (*  sin_p1p2  p2x) (* cos_p1p2 p2y)))
       (setq c_temp2 (- (*  sin_p1p2  p4x) (* cos_p1p2 p4y)))
    
       (setq expt_a2b2  (expt (+ (expt  sin_p1p2 2) (expt  cos_p1p2 2)) 0.5))
       (setq p2_p4_vdist (/ (abs (- c_temp1 c_temp2)) expt_a2b2)); v:直
       (if (> lsp_pitch p2_p4_vdist)
	   (progn
	        (alert (strcat "\n牙距(Pitch)= " (rtos lsp_pitch) " 為不合理!!" " ( 小於" (rtos p2_p4_vdist) "為合理 )"))
	        (exit)
	   );progn
       );if 	 
	     

       (setq p3x (car p3))
       (setq p3y (cadr p3))
       (setq c_temp1 (- (*  sin_p1p2  p3x) (* cos_p1p2 p3y)))
       (setq p3_p4_vdist (/ (abs (- c_temp1 c_temp2)) expt_a2b2))
    
       (setq p11 (polar p1 (+ ang_bp1_p2 a90) (- p2_p4_vdist lsp_pitch)))
       (setq p12 (polar p1 (+ ang_bp1_p2 a90)  p2_p4_vdist ))
       (setq ang_bp11_p1 (angle p11 p1))
       (setq p11end (polar p11 (+ ang_bp11_p1 a90) 10))
       (cond
	     ( (< lsp_pitch p3_p4_vdist)
	       (setq inter_p (inters p11 p11end p3 p4 nil))
             )
	     ( (= lsp_pitch p3_p4_vdist)
	       (setq inter_p p3)
             )
	     ( (> lsp_pitch p3_p4_vdist)
	       (setq inter_p (inters p11 p11end p2 p3 nil))
             )
       );cond
       (setq ss nil)
       (setq ss (ssadd))
       (if (= all_pitch_flag nil)
	   (progn
	        (c:&SL&)
                (command "line" p1 p12 "")
	        (ssadd (entlast) ss)
	   );progn  
       );if	 
       
       
       (c:&tl&)
       (command "line" p11 inter_p "")
      
       (ssadd (entlast) ss)
       (command "mirror" ss "" p1 p2 "N")
       (setvar "osmode" osmode_v)	       
);defun    
    
       
(defun endcirpro(/   all_pitch_flag p1 p2 p3 p4 a90 all_leng ang_bp1_p2 ang_bp2_p1 dist_p1_p2 sin_p1p2 cos_p1p2 p2x p2y p4x p4y
                       p3x p3y c_temp1 c_temp2 expt_a2b2 p2_p4_vdist p3_p4_vdist p11 p12 p11end ang_bp11_p1 inter_p
		       ss
		   )
       (setq a90 (/ pi 2))
       (setq all_leng nil)
       (setq all_pitch_flag nil)
   
       (princ "\n請依照對話框幻燈片 P1 P2 P3 之位置輸入\n")
       (if (= pro_flag 1)
	   (progn
                (setq p1 (getpoint "\np1 (全牙邊線與中心線之交點): "))
                (setq p2 (getpoint p1 "\np2 (圓形端前一線與中心線之交點): "))
                (setq p3 (getpoint p2 "\np3 (外框線與圓形端底線之交點): "))
	   );progn
       );if
       (if (= pro_flag 3)
	   (progn
                (setq p1 (getpoint "\np1 (全牙邊線與中心線之交點): "))
                (setq p2 (getpoint p1 "\np2 (平面端線與中心線之交點): "))
                (setq p3 (getpoint p2 "\np3 (外框線與平面端線之交點): "))
	   );progn
       );if
      
       (setq osmode_v (getvar "osmode"))
       (setvar "osmode" 0)
       (setq ang_bp1_p2 (angle p1 p2));b:base
       (setq ang_bp2_p1 (angle p2 p1))
       (setq dist_p1_p2 (distance p1 p2))
       (if (= lsp_outscrewleng "")
	   (progn
	        (setq lsp_outscrewleng (rtos dist_p1_p2))
	        (setq all_pitch_flag t)
	   );progn  
       );if	 
       (cond ( (>=  (atof lsp_outscrewleng) dist_p1_p2)
	       (setq dist_p1_p2 dist_p1_p2)
	       (setq all_pitch_flag t)
	       
             )
    
             ( (<  (atof lsp_outscrewleng) dist_p1_p2)
	  
	        (setq dist_p1_p2 (atoi lsp_outscrewleng))
	        (setq p1 (polar p2 ang_bp2_p1 dist_p1_p2))
	   
             )
       );cond	     
    
      
       (setq sin_p1p2 (sin ang_bp1_p2))
       (setq cos_p1p2 (cos ang_bp1_p2))
    
       (setq p2x (car p2))
       (setq p2y (cadr p2))
       (setq p3x (car p3))
       (setq p3y (cadr p3))
       (setq c_temp1 (- (*  sin_p1p2  p2x) (* cos_p1p2 p2y)))
       (setq c_temp2 (- (*  sin_p1p2  p3x) (* cos_p1p2 p3y)))
    
       (setq expt_a2b2  (expt (+ (expt  sin_p1p2 2) (expt  cos_p1p2 2)) 0.5))
       (setq p2_p3_vdist (/ (abs (- c_temp1 c_temp2)) expt_a2b2)); v:直
       (if (> lsp_pitch p2_p3_vdist)
	   (progn
	        (alert (strcat "\n牙距(Pitch)= " (rtos lsp_pitch) " 為不合理!!" " ( 小於" (rtos p2_p3_vdist) "為合理 )"))
	        (exit)
	   );progn
       );if 	 
	     

      
    
       (setq p11 (polar p1 (+ ang_bp1_p2 a90) (- p2_p3_vdist lsp_pitch)))
       (setq p12 (polar p1 (+ ang_bp1_p2 a90)  p2_p3_vdist ))
       (setq ang_bp11_p1 (angle p11 p1))
       (setq p11end (polar p11 (+ ang_bp11_p1 a90) (distance p1 p2)))
      
       (setq ss nil)
       (setq ss (ssadd))
       (if (= all_pitch_flag nil)
	   (progn
	        (c:&sl&)
                (command "line" p1 p12 "")
	        (ssadd (entlast) ss)
	   );progn  
       );if	 
      
       
       (c:&tL&)
       (command "line" p11 p11end "")
       (ssadd (entlast) ss)
       (command "mirror" ss "" p1 p2 "N")
       (setvar "osmode" osmode_v)	       
);defun
(defun show_sld_screwline(key sldname col / x y lacol newcol col_v)
     
     (setq x (dimx_tile key))
     (setq y (dimy_tile key))
    
     (start_image key)
     (fill_image 0 0 x y  col)
     
     (slide_image 0 0 x y (strcat Powdesign_sld_PATH sldname))
     (end_image)
    
);defun

(defun sel_show_sld(key sldname)
     (show_sld_screwline "endcir" "endc_phL"  -2)
     (show_sld_screwline "endflat" "endf_phL" -2)
     (show_sld_screwline "endnone" "endn_phL" -2)
     (show_sld_screwline key      sldname  253)
);defun
