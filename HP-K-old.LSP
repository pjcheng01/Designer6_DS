(defun c:hp(/ block_con block_sz)
	(setvar "cmdecho" 0)

	(cond ((setq block_con (ssget "X" (list (cons 0 "INSERT")(cons 2 "A1tzt"))))
		(setq block_sz 1))
	      ((setq block_con (ssget "X" (list (cons 0 "INSERT")(cons 2 "A2tzt"))))
		(setq block_sz 2))
	      ((setq block_con (ssget "X" (list (cons 0 "INSERT")(cons 2 "A3tzt"))))
  		(setq block_sz 3))
	      ((setq block_con (ssget "X" (list (cons 0 "INSERT")(cons 2 "A4tzt"))))
		(setq block_sz 4))
              ((setq block_con (ssget "X" (list (cons 0 "INSERT")(cons 2 "ASMA1tzt"))))
              	(setq block_sz 5))
              ((setq block_con (ssget "X" (list (cons 0 "INSERT")(cons 2 "ASMA2tzt"))))
              	(setq block_sz 6))
              ((setq block_con (ssget "X" (list (cons 0 "INSERT")(cons 2 "ASMA3tzt"))))
		(setq block_sz 7))
 	)

  	(cond ((= 1 block_sz)(hp_plot "A3" "A1"))
	      ((= 2 block_sz)(hp_plot "A3" "A2"))
	      ((= 3 block_sz)(hp_plot "A3" "A3"))
	      ((= 4 block_sz)(hp_plot "A4" "A4"))
	      ((= 5 block_sz)(hp_plot "A3" "A1"))
              ((= 6 block_sz)(hp_plot "A3" "A2"))
              ((= 7 block_sz)(hp_plot "A3" "A3"))
	)
  	(setvar "cmdecho" 1)
)

(defun hp_plot(paper_size paper_style)

	(command "zoom" "e")
     	(setq pp1 '(5 7 0))
     	(setq cmddia_setvar (getvar "cmddia"))
     	(setq ltscale_setvar (getvar "ltscale"))
     	
  	(if (or (= "A3" paper_style)(= "A4" paper_style))
	    (setq scale_size (/ 1.0 (* ltscale_setvar 1)))         ;;出圖比例       A1= A3 * 2
            (setq scale_size "fit")
  	)

  	(command "cmddia" 0)
	(command ".plot" "Y" "MODEL" "HP LaserJet 5100 PCL 6" paper_size "M" "L" "N" "E" scale_size "c" "Y" "aclt.ctb" "Y" "N" "N" "N" "y")
  	;(command ".plot" "Y" "MODEL" "HP..." paper_size "M" "L" "N" "L" scale_size pp1 "Y" "形式表名稱" "N" "N" "N" "N" "N")
  	;(command ".plot" "e" "5" "y" "HP DesignJet 350C" "e" "5" "n" "y" "7" "0" "0.2" "7" "0" "0.2" "7" "0" "0.3" "7" "0" "0.2" "7" "0" "0.2" "7" "0" "0.2" "7" "0" "0.35" "7" "0" "0.2" "7" "0" "0.2" "7" "0" "0.2" "7" "0" "0.2" "7" "0" "0.2" "7" "0" "0.2" "7" "0" "0.2" "7" "0" "0.2" "7" "0" "0.2" "7" "0" "0.2" "7" "0" "0.2"  "x" "n" "m" pp1 paper_size  "0" "n" scale_size "" )
     	(command "cmddia" "1")
  	(prompt (strcat "<<<<   " paper_style "  出圖完成    >>>>"))
     	(command "zoom" "P")

)

(defun c:hp2(/ block_con block_sz)
	(setvar "cmdecho" 0)
  
	(cond ((setq block_con (ssget "X" (list (cons 0 "INSERT")(cons 2 "A1tzt"))))
		(setq block_sz 1))
	      ((setq block_con (ssget "X" (list (cons 0 "INSERT")(cons 2 "A2tzt"))))
		(setq block_sz 2))
	      ((setq block_con (ssget "X" (list (cons 0 "INSERT")(cons 2 "A3tzt"))))
  		(setq block_sz 3))
	      ((setq block_con (ssget "X" (list (cons 0 "INSERT")(cons 2 "A4tzt"))))
		(setq block_sz 4))
              ((setq block_con (ssget "X" (list (cons 0 "INSERT")(cons 2 "ASMA1tzt"))))
              	(setq block_sz 5))
              ((setq block_con (ssget "X" (list (cons 0 "INSERT")(cons 2 "ASMA2tzt"))))
              	(setq block_sz 6))
              ((setq block_con (ssget "X" (list (cons 0 "INSERT")(cons 2 "ASMA3tzt"))))
		(setq block_sz 7))
 	)

  	(cond ((= 1 block_sz)(hp2_plot "較大尺寸：ISO A1  (portrait)" "A1"))
	      ((= 2 block_sz)(hp2_plot "較大尺寸：ISO A2  (landscape)" "A2"))
	      ((= 3 block_sz)(hp2_plot "較大尺寸：ISO A3  (landscape)" "A3"))
	      ((= 4 block_sz)(hp2_plot "較大尺寸：ISO A4  (landscape)" "A4"))
	      ((= 5 block_sz)(hp2_plot "較大尺寸：ISO A1  (portrait)" "A1"))
              ((= 6 block_sz)(hp2_plot "較大尺寸：ISO A2  (landscape)" "A2"))
              ((= 7 block_sz)(hp2_plot "較大尺寸：ISO A3  (landscape)" "A3"))
	)
  	(setvar "cmdecho" 1)
)

(defun hp2_plot(paper_size paper_style)

	(command "zoom" "e")
     	(setq pp1 '(5 7 0))
     	(setq cmddia_setvar (getvar "cmddia"))
     	(setq ltscale_setvar (getvar "ltscale"))
     	(setq scale_size (/ 1.0 (* ltscale_setvar 1)))         ;;出圖比例       A1= A3 * 2

  	(command "cmddia" 0)
	(command ".plot" "Y" "MODEL" "HP DesignJet 500 42 by HP" paper_size "M" "L" "N" "E" scale_size "c" "Y" "aclt.ctb" "Y" "N" "N" "N" "y")
  	;(command ".plot" "e" "5" "y" "HP DesignJet 350C" "e" "5" "n" "y" "7" "0" "0.2" "7" "0" "0.2" "7" "0" "0.3" "7" "0" "0.2" "7" "0" "0.2" "7" "0" "0.2" "7" "0" "0.35" "7" "0" "0.2" "7" "0" "0.2" "7" "0" "0.2" "7" "0" "0.2" "7" "0" "0.2" "7" "0" "0.2" "7" "0" "0.2" "7" "0" "0.2" "7" "0" "0.2" "7" "0" "0.2" "7" "0" "0.2"  "x" "n" "m" pp1 paper_size  "0" "n" scale_size "" )
     	(command "cmddia" "1")
  	(prompt (strcat "<<<<   " paper_style "  出圖完成    >>>>"))
     	(command "zoom" "P")
)
