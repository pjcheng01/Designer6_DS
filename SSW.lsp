;;;
(defun lays# (/ latxt pt sera lays ch lay)
 (setq lay (car (entsel "\nSelect entity layer(s) / <TYPE NAME>: "))
       lays nil
 )
 (if (null lay)
  (progn
   (setq latxt (strcase (getstring "\nEnter layer(s) name: ")))
   (if (/= latxt "")
    (progn
     (setq pt 1 sera 1)
     (while (/= (setq ch (substr latxt pt 1)) "")
      (if (= ch ",")
       (if (> pt sera)
        (progn
         (setq lay (substr latxt sera (- pt sera)) sera (1+ pt))
         (if (and (tblsearch "LAYER" lay) (ssget "x" (list (cons 8 lay))))
          (setq lays (append lays (list lay)))
          (princ (strcat "\nLayer " lay " not existed or empty !"))
         )
        )
        (setq sera (1+ sera))
       )
      )
      (setq pt (1+ pt))
     )
     (if (> pt sera)
      (progn
       (setq lay (substr latxt sera (- pt sera)))
       (if (and (tblsearch "LAYER" lay) (ssget "x" (list (cons 8 lay))))
        (setq lays (append lays (list lay)))
        (princ (strcat "\nLayer " lay " not existed or empty !"))
       )
      )
     )
    )
   )
  )
  (progn
   (princ "\nSelect entity layer(s) / <RETURN to Exit>: ")
   (setq lay (cdr (assoc 8 (entget lay))) lays (append lays (list lay)))
   (princ lay)
   (setq lay (car (entsel "")))
   (while lay
    (setq lay (cdr (assoc 8 (entget lay))) lays (append lays (list lay))
          lay (car (entsel (strcat "," lay)))
    )
   )
  )
 )
 lays
)
(defun sslays# (ents lays / ent sera et)
 (setq ent (ssadd))
 (if (and (not (null ents)) (> (length lays) 0))
  (progn
   (setq sera 0)
   (repeat (sslength ents)
    (setq et (ssname ents sera))
    (if (member (cdr (assoc 8 (entget et))) lays)
     (ssadd et ent)
    )
    (setq sera (1+ sera))
   )
  )
 )
 ent
)
(defun ssw (/ p1 p2 lays ents)
 (setq ents (ssadd))
 (if (or (null #ser#) (not (= (type #ser#) 'REAL)))
  (setq #ser# 0.0)
 )
 (if (or (null @sca$) (not (= (type @sca$) 'REAL)))
  (setq @sca$ 0.0)
 )
 (if (= (+ (* #ser# 2.7) 17.3 @sca$) 40536.0)
  (progn
   (initget 1)
   (setq p1 (getpoint "\nSelect objects' First corner: "))
   (initget 1)
   (setq p2 (getcorner p1 "\nOther corner: ")
         ents (ssget "w" p1 p2)
   )
   (princ "\nObjects' layer(s) -->")
   (setq lays (lays#) ents (sslays# ents lays))
  )
; (princ "\nPlease load [ RIGHT.LSP ] !")
 )
 ents
)
