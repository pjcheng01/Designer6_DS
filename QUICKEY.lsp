(defun c:Ddl()
 (c:autoload)
 (setvar "cmdecho" 0)
 (ch_lt_c "DASHED" "5")
; (setvar "cmdecho" 1)
)
;;粗連續線
(defun c:sl()
  (c:autoload)
 (setvar "cmdecho" 0)
 (ch_lt_c sys_CONT_ltype sys_CONT_ltypecol)
; (setvar "cmdecho" 1)
)
(defun c:ss()
 (c:autoload)
 (setvar "cmdecho" 0)
 (ch_lt_c sys_CONT_ltype sys_CONT_ltypecol)
; (setvar "cmdecho" 1)
)
(defun c:sss()
  (c:autoload)
 (setvar "cmdecho" 0)
 (ch_lt_c sys_CONT_ltype sys_CONT_ltypecol)
; (setvar "cmdecho" 1)
)
;;虛線
(defun c:dl()
  (c:autoload)
 (setvar "cmdecho" 0)
 (ch_lt_c sys_dashed_ltype sys_dashed_ltypecol)
; (setvar "cmdecho" 1)
)
(defun c:dd()
  (c:autoload)
 (setvar "cmdecho" 0)
 (ch_lt_c sys_dashed_ltype sys_dashed_ltypecol)
; (setvar "cmdecho" 1)
)
(defun c:Sdd()
  (c:autoload)
 (setvar "cmdecho" 0)
 (ch_lt_c sys_Sdashed_ltype sys_Sdashed_ltypecol)
; (setvar "cmdecho" 1)
)
(defun c:ddd()
  (c:autoload)
 (setvar "cmdecho" 0)
 (ch_lt_c sys_dashed_ltype sys_dashed_ltypecol)
; (setvar "cmdecho" 1)
)


;;短虛線
(defun c:Sdd()
  (c:autoload)
 (setvar "cmdecho" 0)
 (ch_lt_c sys_Sdashed_ltype sys_Sdashed_ltypecol)
; (setvar "cmdecho" 1)
)

;;中心線
(defun c:cl()
  (c:autoload)
 (setvar "cmdecho" 0)
 (ch_lt_c sys_center_ltype sys_center_ltypecol)
; (setvar "cmdecho" 1)
)
(defun c:cc()
  (c:autoload)
 (setvar "cmdecho" 0)
 (ch_lt_c sys_center_ltype sys_center_ltypecol)
; (setvar "cmdecho" 1)
)
(defun c:ccc()
  (c:autoload)
 (setvar "cmdecho" 0)
 (ch_lt_c sys_center_ltype sys_center_ltypecol)
; (setvar "cmdecho" 1)
)
;;短中心線
(defun c:scl()
  (c:autoload)
 (setvar "cmdecho" 0)
 (ch_lt_c sys_stcenter_ltype sys_stcenter_ltypecol)
; (setvar "cmdecho" 1)
)
(defun c:scc()
  (c:autoload)
 (setvar "cmdecho" 0)
 (ch_lt_c sys_stcenter_ltype sys_stcenter_ltypecol)
; (setvar "cmdecho" 1)
)
(defun c:sccc()
  (c:autoload)
 (setvar "cmdecho" 0)
 (ch_lt_c sys_stcenter_ltype sys_stcenter_ltypecol)
; (setvar "cmdecho" 1)
)
;;假想線
(defun c:pl()
  (c:autoload)
 (setvar "cmdecho" 0)
 (ch_lt_c sys_phantom_ltype  sys_phantom_ltypecol)
; (setvar "cmdecho" 1)
)
(defun c:pp()
  (c:autoload)
 (setvar "cmdecho" 0)
 (ch_lt_c sys_phantom_ltype  sys_phantom_ltypecol)
; (setvar "cmdecho" 1)
)
(defun c:ppp()
  (c:autoload)
 (setvar "cmdecho" 0)
 (ch_lt_c sys_phantom_ltype  sys_phantom_ltypecol)
; (setvar "cmdecho" 1)
)


;;短假想線
(defun c:Spp()
  (c:autoload)
 (setvar "cmdecho" 0)
 (ch_lt_c sys_Sphantom_ltype  sys_Sphantom_ltypecol)
; (setvar "cmdecho" 1)
)

;;細實線
(defun c:tl()
  (c:autoload)
 (setvar "cmdecho" 0)
 (ch_lt_c sys_CONT1_ltype sys_CONT1_ltypecol)
; (setvar "cmdecho" 1)
)
(defun c:tt()
  (c:autoload)
 (setvar "cmdecho" 0)
 (ch_lt_c sys_CONT1_ltype sys_CONT1_ltypecol)
; (setvar "cmdecho" 1)
)
(defun c:ttt()
  (c:autoload)
 (setvar "cmdecho" 0)
 (ch_lt_c sys_CONT1_ltype sys_CONT1_ltypecol)
; (setvar "cmdecho" 1)
)
;;剖面線
(defun c:hl()
  (c:autoload)
 (setvar "cmdecho" 0)
 (ch_lt_c sys_hatch_ltype sys_hatch_ltypecol)
; (setvar "cmdecho" 1)
)
(defun c:hh()
  (c:autoload)
 (setvar "cmdecho" 0)
 (ch_lt_c sys_hatch_ltype sys_hatch_ltypecol)
; (setvar "cmdecho" 1)
)
(defun c:hhh()
  (c:autoload)
 (setvar "cmdecho" 0)
 (ch_lt_c sys_hatch_ltype sys_hatch_ltypecol)
; (setvar "cmdecho" 1)
)
;;切換到零件外形層(ACAD 任何版本皆適用)
(defun c:L0()
  (c:autoload)
  (setvar "cmdecho" 0)
  (command "layer" "s" "0" "" "linetype" "s" sys_CONT_ltype "" "color" sys_CONT_ltypecol)
; (setvar "cmdecho" 1)
  (princ)
)
(defun c:LL0()
  (c:autoload)
  (setvar "cmdecho" 0)
  (command "layer" "s" "0" "" "linetype" "s" sys_CONT_ltype "" "color" sys_CONT_ltypecol)
; (setvar "cmdecho" 1)
  (princ)
)
;;切換到零件外形層(非 LT 版適用)
(defun c:0()
  (c:autoload)
  (setvar "cmdecho" 0)
  (command "layer" "s" "0" "" "linetype" "s" sys_CONT_ltype "" "color" sys_CONT_ltypecol)
; (setvar "cmdecho" 1)
  (princ)
)
;;切換到尺寸層
(defun c:LLD()
  (c:autoload)
  (setvar "cmdecho" 0)
  (clauc sys_dim_layer sys_dim_layercol "CONTINUOUS")
  (ch_lt_c "BYLAYER" "BYLAYER")
;  (setvar "cmdecho" 1)
)
(defun c:d()
  (c:autoload)
  (setvar "cmdecho" 0)
  (clauc sys_dim_layer sys_dim_layercol "CONTINUOUS")
  (ch_lt_c "BYLAYER" "BYLAYER")
;  (setvar "cmdecho" 1)
)
;;切換到文字層
(defun c:t()
  (c:autoload)
  (setvar "cmdecho" 0)
  (clauc sys_text_layer sys_text_layercol "CONTINUOUS")
  (ch_lt_c "BYLAYER" "BYLAYER")
; (setvar "cmdecho" 1)
)
(defun c:LLT()
  (c:autoload)
  (setvar "cmdecho" 0)
  (clauc sys_text_layer sys_text_layercol "CONTINUOUS")
  (ch_lt_c "BYLAYER" "BYLAYER")
; (setvar "cmdecho" 1)
)
;;切換到零件外形層
(defun c:by()
  (c:autoload)
  (setvar "cmdecho" 0)
  (ch_lt_c "BYLAYER" "BYLAYER")
; (setvar "cmdecho" 1)
)
;;切換到投影線層
;(
