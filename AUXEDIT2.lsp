;;功能說明: Power Offset 變換線型
(defun aoff_to_which_ltype(newltype newcolor / offent ent1 data0 offent10 p1 entnum)
   (setvar "cmdecho" 0)
   (cond
;    ((null ofdist)
;      (initget "T")
;      (setq ofdist (getdist "\n指定 Offset 距離[通過(T)]<1.00>:"))
;      (cond
;      (if (null ofdist) (setq ofdist 1) (setq ofdist "T"))
;      );cond
;    )
     ((or (= "T" ofdist)(null ofdist))
       (initget "T")
       (setq ofdist (getdist "\n指定 Offset 距離[通過(T)]<通過>:"))
       (if (null ofdist) (setq ofdist "T"))
     )
     (T
       (if (/= (type ofdist) (type "abc")) (setq olddist ofdist) (setq olddist 1 ofdist 1))
       (initget "T")
       (setq ofdist (getdist (strcat "\n指定 Offset 距離[通過(T)]<" (rtos ofdist 2 4) ">:")))
       (if (null ofdist) (setq ofdist olddist))
     );
   );
   (setq offent (entsel "\n選擇要偏移複製的物件或 <結束>:"))
   (while (/= offent nil)
         (if (= ofdist "T")
           (progn
             (setq p1 (getpoint "\n通過點: "))
             (command "offset" "t" (car offent) p1 "")
           )
           (progn
             (setq p1 (getpoint "\n指定要在那一側偏移複製: "))
             (command "offset" ofdist (car offent) p1 "")
           )
         );if
         (command "change" "l" "" "p" "c" newcolor "lt" newltype "")
         (if (and entnum (/= (sslength entnum) 1))
           (progn
                 (command "explode" (entlast))
                 (command "explode" offent)
           );progn
         );if
         (setq entnum nil)
         (setq offent (entsel "\n選擇要偏移複製的物件或 <結束>:"))
   );if
   (setvar "cmdecho" 1)
   (princ)
)

(defun ch_to_objlayer(objlayer)
   (setvar "cmdecho" 0)
   (princ (strcat "\n選擇要變換到 " objlayer " 層的圖形: "))
   (setq selent (ssget))
   (while (/= nil selent)
     (setq oldlayer (getvar "clayer"))
     (if (and (= objlayer sys_dim_layer)(null (tblsearch "layer" objlayer))) (C:&D&))
     (if (and (= objlayer sys_text_layer)(null (tblsearch "layer" objlayer))) (C:&t&))
     (command "change" "p" "" "p" "la" objlayer "")
     (setvar "clayer" oldlayer)
     (princ (strcat "\n選擇要變換到 " objlayer " 層的圖形: "))
     (setq selent (ssget))
   )
   (princ (strcat "\n所選擇的圖形已經變換到 " objlayer " 層!" ))
   (setvar "cmdecho" 1)
   (princ)
)
