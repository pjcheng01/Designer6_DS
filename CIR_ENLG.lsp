;;;
(defun c:cir_enLg(/ s_dat c_cor moveent c_rad c_ent spt1 spt2 ss_get man_lst s_sca s_loc
              cecmd boundary ss_list)
  ;; DraftSight: 移除加密狗 WHILE 迴圈
  (setq cecmd (getvar "cmdecho"))

  (setq osmode_OLD    (getvar "osmode"))
  (setq plinewid_OLD  (getvar "plinewid"))
  (setq orthomode_OLD (getvar "orthomode"))

  (setvar "cmdecho" 0)
  (setvar "osmode" 512)
  (setvar "orthomode" 1)

  (setq *error_CirEnLgOLD *error*)
  (setq *error* *error_CirEnLg)


  (setq s_dat (get_section_circle_cirenlg))
  (setq c_cor (nth 0 s_dat) c_rad (nth 1 s_dat))
  (princ "\n詳圖位置:")
  (command  "move" @c_circle1 "" c_cor pause)
  (command "erase" @c_circle1 "")
  (setq #moveent (entlast))
  (setq s_loc (getvar "lastpoint") )
  (setq spt1 (polar c_cor (dtor_cirenlg  45.0) (* (sqrt 2.0) c_rad)))
  (setq spt2 (polar c_cor (dtor_cirenlg 225.0) (* (sqrt 2.0) c_rad)))
  (setq ss_get (ssget "c" spt1 spt2))
  (ssdel #moveent ss_get)
  (setq man_lst (copy_scale_ent_cirenlg ss_get 1 s_loc c_cor c_rad))
  (setq boundary (nth 0 man_lst))
  (setq ss_list  (nth 1 man_lst))
  (generate_section_cirenlg boundary ss_list)
  (command "cmdecho" cecmd)
  (get_all_element_cirenlg #moveent)
  (setq s_sca (getreal "\n比例<1>:"))
  (if (= s_sca nil)
      (setq s_sca 1)
  )
  (command "scale" @all_set "" s_loc s_sca)
  (princ)

  (setvar "osmode"    osmode_OLD)
  (setvar "plinewid"  plinewid_OLD)
  (setvar "orthomode" orthomode_OLD)
  ;; removed FFF
)

(defun *error_CirEnLg(msg)
     (setvar "osmode"    osmode_OLD)
     (setvar "plinewid"  plinewid_OLD)
     (setvar "orthomode" orthomode_OLD)
     (setq *error*       *error_CirEnLgOLD)
)


(defun get_all_element_cirenlg(#moveent  / ent)
  (setq @all_set (ssadd))
  (while (/= (setq  ent (entnext #moveent)) nil)
    (ssadd ent @all_set)
    (setq #moveent ent )
  )
   
)  
(defun copy_scale_ent_cirenlg(ss_get s_sca s_loc c_cor c_rad / ss_ent last_ent c_last
                                                       ent)
  (setq last_ent (entlast))
  (if ss_get (command "copy" ss_get "" c_cor s_loc))
  (setq ss_ent (get_copy_ent_cirenlg last_ent))
  ;(entdel @c_circle)
  (mem_curset)
  (c:&pl&)
  (command "circle" s_loc c_rad)
  (rt_to_old_set)
  
  (setq c_last (entlast))
  (if (not (var_eqp_cirenlg s_sca 1.0))
    (progn
      (command "scale" c_last "" s_loc s_sca)
      (foreach ent ss_ent (command "scale" ent "" s_loc s_sca))
    )
  )
 
  (list c_last ss_ent)
)

(defun generate_section_cirenlg(c_last ss_ent / ent cecmd ent_num)
  (setq ent_num (rtos (length ss_ent) 2 0))
  ;(prompt (strcat "\nProcesing " ent_num " entities,waiting"))
  ;(prompt "\nStart")
  (prompt (strcat "\n處理 " ent_num " 圖元, 請等待"))
  (foreach ent ss_ent
    (setq data (entget ent))
    (cond
      ((= (ent_dat_cirenlg 0 ent) "LINE")
       (trim_line_cirenlg ent c_last)
        
      )
      ((= (ent_dat_cirenlg 0 ent) "ARC")
       (trim_arc_cirenlg ent c_last)
       
      )
      ((= (ent_dat_cirenlg 0 ent) "CIRCLE")
       (mem_curset)
       (c:&pl&)
       (trim_circle_cirenlg ent c_last)
       (rt_to_old_set)
       
      )
      ((= (ent_dat_cirenlg 0 ent) "INSERT") 
      )
      ((= (ent_dat_cirenlg 0 ent) "SOLID")
       (trim_solid_cirenlg ent c_last)
       
      )
      ((= (ent_dat_cirenlg 0 ent) "POINT")
       (trim_pt_txt_cirenlg ent c_last)
       
      )
      ((= (ent_dat_cirenlg 0 ent) "TEXT")
       (trim_pt_txt_cirenlg ent c_last)
       
      )
    )
   ; (prompt ".")
  )
  ;(prompt "done!")
  (princ)
)

(defun trim_pt_txt_cirenlg(ent c_last)
  (setq c_rad (ent_dat_cirenlg 40 c_last) c_cor (ent_dat_cirenlg 10 c_last))
  (setq ent_ins (ent_dat_cirenlg 10 ent))
  (if (not (pt_in_circle_cirenlg c_cor c_rad ent_ins))
    (entdel ent)
  )
  (princ)
)

(defun trim_solid_cirenlg(ent c_last)
  (setq c_rad (ent_dat_cirenlg 40 c_last) c_cor (ent_dat_cirenlg 10 c_last))
  (setq sod_pt1 (ent_dat_cirenlg 10 ent))
  (setq sod_pt2 (ent_dat_cirenlg 11 ent))
  (setq sod_pt3 (ent_dat_cirenlg 12 ent))
  (setq sod_pt4 (ent_dat_cirenlg 13 ent))
  (if (or (not (pt_in_circle_cirenlg c_cor c_rad sod_pt1))
          (not (pt_in_circle_cirenlg c_cor c_rad sod_pt2))
          (not (pt_in_circle_cirenlg c_cor c_rad sod_pt3))
          (not (pt_in_circle_cirenlg c_cor c_rad sod_pt4)))
    (entdel ent)
  )
  (princ)
)

(defun trim_circle_cirenlg(ent c_last / rad1 rad2 cen1 cen2 xc1 yc1 xc2 yc2 #1 #2 temp
                             si1 si2 int_x1 int_y1 int_p1 int_x2 int_y2 int_p2)
  (setq rad1 (ent_dat_cirenlg 40 c_last) cen1 (ent_dat_cirenlg 10 c_last))
  (setq c_cor cen1 c_rad rad1)
  ;
  (setq rad2 (ent_dat_cirenlg 40 ent) cen2 (ent_dat_cirenlg 10 ent))
  (setq ent_rad rad2 ent_cen cen2)
  ;
  (setq chg_c_dat (chg_c_p_cirenlg cen1 cen2 rad1 rad2))
  (setq cen1 (nth 0 chg_c_dat) cen2 (nth 1 chg_c_dat))
  (setq rad1 (nth 2 chg_c_dat) rad2 (nth 3 chg_c_dat))
  ;
  (cond
    ((and (< (setq #1 (distance cen1 cen2)) (+ rad1 rad2))
          (> (setq #1 (distance cen1 cen2)) (abs (- rad1 rad2))))
     (setq xc1 (nth 0 cen1) yc1 (nth 1 cen1))
     (setq xc2 (nth 0 cen2) yc2 (nth 1 cen2))
     (setq #2 (/ (+ (expt rad1 2.0) (expt #1 2.0) (- (expt rad2 2.0)))
                 (* 2.0 rad1 #1)))
     (setq si1 (atan (/ (sqrt (- 1.0 (expt #2 2.0))) #2)))
     (setq si2 (atan (/ (- yc2 yc1) (- xc2 xc1))))
     (setq int_x1 (+ xc1 (* rad1 (cos (+ si1 si2)))))
     (setq int_y1 (+ yc1 (* rad1 (sin (+ si1 si2)))))
     (setq int_p1 (list int_x1 int_y1 0.0))
     ;
     (setq int_x2 (+ xc1 (* rad1 (cos (- si2 si1)))))
     (setq int_y2 (+ yc1 (* rad1 (sin (- si2 si1)))))
     (setq int_p2 (list int_x2 int_y2 0.0))
     ;
     (setq ang1 (angle ent_cen int_p1))
     (setq ang2 (angle ent_cen int_p2))
     (setq min_ang (min ang1 ang2))
     (setq max_ang (max ang1 ang2))
     (setq trim_ang1 (+ max_ang (* 0.5 (- max_ang min_ang))))
     (setq trim_ang2 (+ min_ang (* 0.5 (- max_ang min_ang))))
     (setq trim_p1 (polar ent_cen trim_ang1 ent_rad))
     (setq trim_p2 (polar ent_cen trim_ang2 ent_rad))
     (if (pt_in_circle_cirenlg c_cor c_rad trim_p1)
       (setq trim_p trim_p2)
       (setq trim_p trim_p1)
     )
     (command "trim" c_last "" (list ent trim_p) "")
    )
    ((>= (distance cen1 cen2) (+ rad1 rad2))
     (entdel ent)
    )
  )
  (princ)
)

(defun chg_c_p_cirenlg(cen1 cen2 rad1 rad2 / temp)
  (if (> (nth 0 cen1) (nth 0 cen2))    
    (progn                             
      (setq temp rad1)                 
      (setq rad1 rad2)
      (setq rad2 temp)
      (setq temp cen1)
      (setq cen1 cen2)
      (setq cen2 temp)
    )
  )
  (list cen1 cen2 rad1 rad2)
)

(defun trim_arc_cirenlg(ent c_last / rad1 rad2 cen1 cen2 xc1 yc1 xc2 yc2 #1 #2 temp
                             si1 si2 int_x1 int_y1 int_p1 int_x2 int_y2 int_p2)
  (setq rad1 (ent_dat_cirenlg 40 c_last) cen1 (ent_dat_cirenlg 10 c_last))
  (setq c_cor cen1 c_rad rad1)
  ;
  (setq rad2 (ent_dat_cirenlg 40 ent) cen2 (ent_dat_cirenlg 10 ent))
  (setq ent_rad rad2 ent_cen cen2)
  (setq st_p  (cal_arc_p_cirenlg ent  "ST"))
  (setq end_p (cal_arc_p_cirenlg ent "END"))
  (setq st_ang  (ent_dat_cirenlg 50 ent))
  (setq end_ang (ent_dat_cirenlg 51 ent))
  ;
  (setq chg_c_dat (chg_c_p_cirenlg cen1 cen2 rad1 rad2))
  (setq cen1 (nth 0 chg_c_dat) cen2 (nth 1 chg_c_dat))
  (setq rad1 (nth 2 chg_c_dat) rad2 (nth 3 chg_c_dat))
  ;
  (if (and (< (setq #1 (distance cen1 cen2)) (+ rad1 rad2))
           (> (setq #1 (distance cen1 cen2)) (abs (- rad1 rad2))))
    (progn
      (setq xc1 (nth 0 cen1) yc1 (nth 1 cen1))
      (setq xc2 (nth 0 cen2) yc2 (nth 1 cen2))
      (setq #2 (/ (+ (expt rad1 2.0) (expt #1 2.0) (- (expt rad2 2.0)))
                  (* 2.0 rad1 #1)))
      (setq si1 (atan (/ (sqrt (- 1.0 (expt #2 2.0))) #2)))
      (setq si2 (atan (/ (- yc2 yc1) (- xc2 xc1))))
      (setq int_x1 (+ xc1 (* rad1 (cos (+ si1 si2)))))
      (setq int_y1 (+ yc1 (* rad1 (sin (+ si1 si2)))))
      (setq int_p1 (list int_x1 int_y1 0.0))
      ;
      (setq int_x2 (+ xc1 (* rad1 (cos (- si2 si1)))))
      (setq int_y2 (+ yc1 (* rad1 (sin (- si2 si1)))))
      (setq int_p2 (list int_x2 int_y2 0.0))
      (cond                                              
        ((and (pt_in_circle_cirenlg c_cor c_rad st_p)
              (pt_in_circle_cirenlg c_cor c_rad end_p))
         (setq ang1 (angle ent_cen int_p1))
         (setq ang2 (angle ent_cen int_p2))
         (setq min_ang (min ang1 ang2))
         (setq max_ang (max ang1 ang2))
         (setq trim_ang1 (+ max_ang (* 0.5 (- max_ang min_ang))))
         (setq trim_ang2 (+ min_ang (* 0.5 (- max_ang min_ang))))
         (setq trim_p1 (polar ent_cen trim_ang1 ent_rad))
         (setq trim_p2 (polar ent_cen trim_ang2 ent_rad))
         (if (pt_in_circle_cirenlg c_cor c_rad trim_p1)
           (setq trim_p trim_p2)
           (setq trim_p trim_p1)
         )
         (command "trim" c_last "" (list ent trim_p) "")
        )
        ((and (not (pt_in_circle_cirenlg c_cor c_rad st_p))      
              (not (pt_in_circle_cirenlg c_cor c_rad end_p)))
         (command "trim" c_last "" (list ent end_p) "")
         (command "trim" c_last "" (list ent st_p) "")
         ;
         (if (and (coor_eqp_cirenlg (cal_arc_p_cirenlg ent  "ST") st_p)
                  (coor_eqp_cirenlg (cal_arc_p_cirenlg ent "END") end_p))
           (entdel ent)
         )
        )
        ((and (pt_in_circle_cirenlg c_cor c_rad st_p)            
              (not (pt_in_circle_cirenlg c_cor c_rad end_p)))
         (command "trim" c_last "" (list ent end_p) "")
        )
        ((and (not (pt_in_circle_cirenlg c_cor c_rad st_p))      
              (pt_in_circle_cirenlg c_cor c_rad end_p))
         (command "trim" c_last "" (list ent st_p) "")
        )
      )
    )
    ;--------2003.02.13 SAM--------
    ;(entdel ent)
    ;------------------------------
  )
  (princ)
)

(defun cal_arc_p_cirenlg(ent ptype / rad cen st_ang end_ang pt)
  (setq rad (ent_dat_cirenlg 40 ent) cen (ent_dat_cirenlg 10 ent))
  (if (= ptype "ST")
    (setq  st_ang (ent_dat_cirenlg 50 ent) pt (polar cen  st_ang rad))
    (setq end_ang (ent_dat_cirenlg 51 ent) pt (polar cen end_ang rad))
  )
  pt
)

(defun trim_line_cirenlg(ent c_last / c_rad c_cor st_p end_p ent cen rad yc xc
                              lin_m arc_t #1 #2 #3 int_x1 int_x2 int_y1
                              int_y2 int_p1 int_p2)
  (setq c_rad (ent_dat_cirenlg 40 c_last) c_cor (ent_dat_cirenlg 10 c_last))
  (setq st_p (ent_dat_cirenlg 10 ent) end_p (ent_dat_cirenlg 11 ent))
  ;
  (setq x0 (nth 0  st_p) y0 (nth 1  st_p))
  (setq x1 (nth 0 end_p) y1 (nth 1 end_p))
  ;
  (setq center c_cor)
  (setq radius c_rad)
  ;
  (setq @error 0.0001)
  (setq xc (car center) yc (cadr center))
  (if (<= (abs (- x1 x0)) @error)
    (setq lin_m (/ (- y1 y0) @error))
    (setq lin_m (/ (- y1 y0) (- x1 x0)))
  )
  (setq arc_t (- y0 (* lin_m x0) yc))
  (setq #1 (- (* 2.0 lin_m arc_t) (* 2.0 xc)))                       
  (setq #2 (+ (expt lin_m 2.0) 1.0))                                
  (setq #3 (- (expt arc_t 2.0) (expt radius 2.0) (- (expt xc 2.0)))) 
  (setq #4 (- (expt #1 2.0) (* 4.0 #2 #3)))                          
  ;
  (if (or (> (abs #4) @maxval) (>= #4 0.0))
    (progn
      (setq #4 (abs #4))
      (setq int_x1 (/ (+ (- #1) (sqrt #4)) (* 2.0 #2)))
      (setq int_y1 (+ y0 (* lin_m (- int_x1 x0))))
      (setq int_p1 (list int_x1 int_y1 0.0))
      ;
      (setq int_x2 (/ (- (- #1) (sqrt #4)) (* 2.0 #2)))
      (setq int_y2 (+ y0 (* lin_m (- int_x2 x0))))
      (setq int_p2 (list int_x2 int_y2 0.0))
      ;
      (cond                                              
        ((and (pt_in_circle_cirenlg c_cor c_rad st_p)
              (pt_in_circle_cirenlg c_cor c_rad end_p))
        )
        ((and (not (pt_in_circle_cirenlg c_cor c_rad st_p))      
              (not (pt_in_circle_cirenlg c_cor c_rad end_p)))
         (command "trim" c_last "" (list ent end_p) "")
         (command "trim" c_last "" (list ent st_p) "")
         ;
         (if (and (coor_eqp_cirenlg (ent_dat_cirenlg 10 ent) st_p)
                  (coor_eqp_cirenlg (ent_dat_cirenlg 11 ent) end_p))
           (entdel ent)
         )
        )
        ((and (pt_in_circle_cirenlg c_cor c_rad st_p)            
              (not (pt_in_circle_cirenlg c_cor c_rad end_p)))
         (command "trim" c_last "" (list ent end_p) "")
        )
        ((and (not (pt_in_circle_cirenlg c_cor c_rad st_p))      
              (pt_in_circle_cirenlg c_cor c_rad end_p))
         (command "trim" c_last "" (list ent st_p) "")
        )
      )
    )
    (entdel ent)
  )
  (princ)
)

(defun get_section_circle_cirenlg(/ flag track track_chk track_pt cen_cor c_rad c_last
                             count)
  (setq flag "t")
  (setq cen_cor (getpoint "\n截取時, 詳圖之中心位置:"))
  ;
  (prompt "\n")
  (setq cel (getvar "celtype"))
  (setq col (getvar "cecolor"))
  (mem_curset)
  (c:&pl&)
 ; (command "linetype" "s" "dashed" "")
  (command "circle" cen_cor pause)
  (rt_to_old_set)
  (setq @c_circle (entlast))
  (setq c_rad (ent_dat_cirenlg 40 (entlast)))
  (command "copy" @c_circle "" cen_cor cen_cor)
  (setq @c_circle1 (entlast))
  (command "linetype" "s" cel "")
  (command "color" col)
  ;(entdel @c_circle)
  ;
  (list cen_cor c_rad s_loc )
)

(defun pt_in_circle_cirenlg(c_cor c_rad pt)
  (if (<= (distance pt c_cor) c_rad)
    t
    nil
  )
)

(defun get_copy_ent_cirenlg(last_ent / ent ss_ent)
  (explode_copy_ent_cirenlg last_ent)
  ;
  (while (/= (setq ent (entnext last_ent)) nil)
    (if (and (/= (ent_dat_cirenlg 0 ent) "SEQEND")
             (/= (ent_dat_cirenlg 0 ent) "VERTEX"))
      (setq ss_ent (cons ent ss_ent))
    )
    (setq last_ent ent)
  )
  ;
  ss_ent
)

(setq #explode_limit 0.0001)
(defun explode_copy_ent_cirenlg(last_ent / ent xfa yfa)
  (while (/= (setq ent (entnext last_ent)) nil)
    (cond
      ((or (= (ent_dat_cirenlg 0 ent) "LWPOLYLINE")
           (= (ent_dat_cirenlg 0 ent) "POLYLINE")
       )           
       (command "explode" ent)
      )
      ((= (ent_dat_cirenlg 0 ent) "DIMENSION")
       (setq clay (getvar "clayer"))
       (command "layer" "s" (ent_dat_cirenlg 8 ent) "")
       (command "explode" ent)
       (setvar "clayer" clay)
      )
      ((= (ent_dat_cirenlg 0 ent) "INSERT")
       (setq xfa (ent_dat_cirenlg 41 ent))
       (setq yfa (ent_dat_cirenlg 42 ent))
       (if (or (<= xfa #explode_limit)
               (<= yfa #explode_limit)
               (not (var_eqp_cirenlg xfa yfa)))
         ;(prompt "\n Pass not uniformly and positively scaled insert !")
         (prompt "\n 不均勻明確比例插入!")
         (command "explode" ent)
       )
      )
    )
    (setq last_ent ent)
  )
  ;
  (princ)
)

(defun get_ss_ent_cirenlg(ss_get / count ss_ent)
  (setq count 0)
  (while (<= count (1- (sslength ss_get)))
    (setq ss_ent (cons (ssname ss_get count) ss_ent))
    (setq count (1+ count))
  )
  ss_ent
)

(defun coor_eqp_cirenlg(coor1 coor2)
  (cond
    ((< (coor_len_cirenlg (coor_sub_cirenlg coor1 coor2)) 0.00000001)
     t
    )
    (t
     nil
    )
  )
)

(defun coor_len_cirenlg(coor)
  (sqrt (+ (expt (car coor) 2) (expt (cadr coor) 2) (expt (caddr coor) 2)))
)

(defun coor_sub_cirenlg(coor1 coor2)
  (list (- (car coor1) (car coor2))
        (- (cadr coor1) (cadr coor2))
        (- (caddr coor1) (caddr coor2)))
)

(defun var_eqp_cirenlg(var1 var2)
  (cond
    ((< (abs (- var1 var2)) 0.00000001)
     t
    )
    (t
     nil
    )
  )
)

(defun atom_del_cirenlg(atom_ent dbf_list)
  (append (reverse (cdr (member atom_ent (reverse dbf_list))))
          (cdr (member atom_ent dbf_list)))
)

(defun dtor_cirenlg(x)
  (* x (/ pi 180.0))
)

(defun ent_dat_cirenlg(flag ent)
  (cdr (assoc flag (entget ent)))
)

(defun rtod_cirenlg(x)
  (* x (/ 180.0 pi))
)
